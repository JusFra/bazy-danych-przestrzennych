FME workspace cw12.fmw

Parameters:
- DestDataset_FILEGDB =
- DestDataset_GEOJSON =
- DestDataset_GEOJSON_3 =
- FEATURE_TYPES =
- FEATURE_TYPES_2 =
- FEATURE_TYPES_3 =
- FEATURE_TYPES_4 =
- SourceDataset_CSV2 =
- SourceDataset_SHAPEFILE =
- SourceDataset_SHAPEFILE_6 =
- SourceDataset_SHAPEFILE_8 =
- SourceDataset_SHAPEFILE_9 =

Readers:
- CSV2_1: CSV2 from $(SourceDataset_CSV2)
- SHAPEFILE_1: SHAPEFILE from $(SourceDataset_SHAPEFILE_6) in DHDN.Berlin/Cassini
- SHAPEFILE_2: SHAPEFILE from $(SourceDataset_SHAPEFILE_9) in DHDN.Berlin/Cassini
- SHAPEFILE_3: SHAPEFILE from $(SourceDataset_SHAPEFILE_8) in DHDN.Berlin/Cassini
- SHAPEFILE_4: SHAPEFILE from $(SourceDataset_SHAPEFILE) in DHDN.Berlin/Cassini

Writers:
- GEOJSON_1: GEOJSON to $(DestDataset_GEOJSON)
- GEOJSON_2: GEOJSON to $(DestDataset_GEOJSON_3)
- FILEGDB_1: FILEGDB to $(DestDataset_FILEGDB)

CSV (reader CSV2_1)
    attributes: x x_coordinate, y y_coordinate
    -> VertexCreator
VertexCreator
    MEASURE_TYPE = Continuous
    MODE_NAME = Replace with Point
    XVAL = @Value(x)
    YVAL = @Value(y)
    -> LineBuilder
LineBuilder
    ACCUM_INPUT_ATTRS = Use Attributes From One Feature
    REMOVE_DUPLICATES = NO
    LINE -> Reprojector
Reprojector
    DEST = DHDN.Berlin/Cassini
    INTERPOLATION_TYPE_NAME = Nearest Neighbor
    RASTER_CELL_SIZE = Preserve Cells
    RASTER_TOLERANCE = 0.0
    REPROJECTED -> ShortestPathFinder [FROM-TO]
    REPROJECTED -> ShortestPathFinder_2 [FROM-TO]
T2019_KAR_STREETS (reader SHAPEFILE_2)
    attributes: LINK_ID long, ST_NAME varchar(254), REF_IN_ID long, NREF_IN_ID long, FUNC_CLASS varchar(1), SPEED_CAT varchar(1), FR_SPEED_L long, TO_SPEED_L long, DIR_TRAVEL varchar(1)
    -> Tester
Tester
    BOOL_OP = OR
    COMPOSITE_TEST = 1
    TEST_CLAUSE = TEST @Value(DIR_TRAVEL) = B
    TEST_MODE = TEST
    PASSED -> AttributeManager
    FAILED -> AttributeManager_2
AttributeManager
    ATTR_TABLE:
      SET_TO ForwardCost = @Evaluate(1*@Length())
      SET_TO ReverseCost = @Evaluate(1*@Length())
    -> ShortestPathFinder_2 [NETWORK]
AttributeManager_2
    ATTR_TABLE:
      SET_TO ForwardCost = @Evaluate(1*@Length())
      SET_TO ReverseCost = @Evaluate(9999*@Length())
    -> ShortestPathFinder_2 [NETWORK]
ShortestPathFinder_2
    ALLOW_UTURNS = Yes
    REORDER_CHOICE = None
    SNAP_POINTS = Yes
    SNAP_TOLERANCE = 200
    WEIGHT_ATTR_1 = ForwardCost
    WEIGHT_ATTR_2 = ReverseCost
    WEIGHT_ATTR_CHOICE = BY_TWO_ATTRIBUTES
    PATH -> Inspector_2
    PATH -> Bufferer
    PATH -> SpatialFilter_4 [Filter]
Inspector_2
Bufferer
    ANGLE = 1
    CAP_STYLE = Arc
    CORNER_STYLE = Arc
    MODE = AREA
    OFFSET = 5
    OFFSET_UNITS = METERS
    PRECISION = APPROX
    BUFFERED -> SpatialFilter [Filter]
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> ShortestPathFinder [NETWORK]
ShortestPathFinder
    ALLOW_UTURNS = Yes
    REORDER_CHOICE = None
    SNAP_POINTS = Yes
    SNAP_TOLERANCE = 200
    WEIGHT_ATTR_CHOICE = BY_LENGTH
    PATH -> Inspector
    PATH -> Bufferer_2
    PATH -> SpatialFilter_3 [Filter]
Inspector
Bufferer_2
    ANGLE = 1
    CAP_STYLE = Arc
    CORNER_STYLE = Arc
    MODE = AREA
    OFFSET = 5
    OFFSET_UNITS = METERS
    PRECISION = APPROX
    BUFFERED -> SpatialFilter_2 [Filter]
T2019_KAR_STREET_NODE (reader SHAPEFILE_4)
    attributes: NODE_ID long, LINK_ID long, POINT_NUM long, Z_LEVEL long, INTERSECT varchar(1), LAT number(31,15), LON number(31,15)
    -> SpatialFilter_3 [Candidate]
    -> SpatialFilter_4 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    CALCULATION_MODE = NUMERIC
    FEAT_STATS = _predicate,NUMERIC_MODE,MIN,MAX,COUNT,SUM,MEAN,MEDIAN,NUMERIC,VALUE_COUNT,,STDEV_S,,,;_total_cost,NUMERIC_MODE,MIN,MAX,COUNT,SUM,MEAN,MEDIAN,NUMERIC,VALUE_COUNT,,STDEV_S,,,;fme_feature_type,NUMERIC_MODE,MIN,MAX,COUNT,SUM,MEAN,MEDIAN,NUMERIC,VALUE_COUNT,,STDEV_S,,,;INTERSECT,NUMERIC_MODE,MIN,MAX,COUNT,SUM,MEAN,MEDIAN,NUMERIC,VALUE_COUNT,,STDEV_S,,,;POINT_NUM,NUMERIC_MODE,MIN,MAX,COUNT,SUM,MEAN,MEDIAN,NUMERIC,VALUE_COUNT,,STDEV_S,,,;Z_LEVEL,NUMERIC_MODE,MIN,MAX,COUNT,SUM,MEAN,MEDIAN,NUMERIC,VALUE_COUNT,,STDEV_S,,,
    SUMMARY -> T2019_KAR_STREET_NODE (writer FILEGDB_1)
T2019_KAR_STREET_NODE (writer FILEGDB_1)
    attributes: NODE_ID int, LINK_ID int, POINT_NUM int, Z_LEVEL int, INTERSECT text(1), LAT double, LON double
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_2
StatisticsCalculator_2
    CALCULATION_MODE = NUMERIC
    FEAT_STATS = _predicate,NUMERIC_MODE,MIN,MAX,COUNT,SUM,MEAN,MEDIAN,NUMERIC,VALUE_COUNT,,STDEV_S,,,;_total_cost,NUMERIC_MODE,MIN,MAX,COUNT,SUM,MEAN,MEDIAN,NUMERIC,VALUE_COUNT,,STDEV_S,,,;fme_feature_type,NUMERIC_MODE,MIN,MAX,COUNT,SUM,MEAN,MEDIAN,NUMERIC,VALUE_COUNT,,STDEV_S,,,;INTERSECT,NUMERIC_MODE,MIN,MAX,COUNT,SUM,MEAN,MEDIAN,NUMERIC,VALUE_COUNT,,STDEV_S,,,;POINT_NUM,NUMERIC_MODE,MIN,MAX,COUNT,SUM,MEAN,MEDIAN,NUMERIC,VALUE_COUNT,,STDEV_S,,,;Z_LEVEL,NUMERIC_MODE,MIN,MAX,COUNT,SUM,MEAN,MEDIAN,NUMERIC,VALUE_COUNT,,STDEV_S,,,
    SUMMARY -> T2019_KAR_STREET_NODE00 (writer FILEGDB_1)
T2019_KAR_STREET_NODE00 (writer FILEGDB_1)
    attributes: NODE_ID int, LINK_ID int, POINT_NUM int, Z_LEVEL int, INTERSECT text(1), LAT double, LON double
T2019_KAR_POI_TABLE (reader SHAPEFILE_3)
    attributes: POI_ID long, LINK_ID long, TYPE varchar(250), POI_NAME varchar(250), ST_NAME varchar(250), LAT number(31,15), LON number(31,15)
    -> SpatialFilter [Candidate]
    -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> T2019_KAR_POI_TABLE00 (writer GEOJSON_2)
T2019_KAR_POI_TABLE00 (writer GEOJSON_2)
    attributes: POI_ID int, LINK_ID int, TYPE string, POI_NAME string, ST_NAME string, LAT float, LON float
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> T2019_KAR_POI_TABLE (writer GEOJSON_2)
T2019_KAR_POI_TABLE (writer GEOJSON_2)
    attributes: POI_ID int, LINK_ID int, TYPE string, POI_NAME string, ST_NAME string, LAT float, LON float
